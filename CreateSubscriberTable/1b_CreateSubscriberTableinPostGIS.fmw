FME workspace 1b_CreateSubscriberTableinPostGIS.fmw
Title: Location-based push notifications for Android and iOS - FME Cloud 2014
Description: Use the FME mobile apps to send and receive location-based push notifications on Android and iOS. 
This package configures a simple notification service in FME Server, which provides a publish and subscribe capability for notifications. The FME Reporter and FME Alerts apps connect up to the notification service to send and receive location-based notifications. 
This package is provided for demo purposes. Feel free to study and extend it.
About Mobile Apps
http://fmepedia.safe.com/articles/Samples_and_Demos/Simple-Tracker-demo-for-FME-Mobile-Apps
http://fmepedia.safe.com/articles/How_To/Android-mobile-apps-tips-tricks
http://fmepedia.safe.com/articles/How_To/FME-Mobile-Apps
http://fmepedia.safe.com/articles/How_To/FME-Server-Notifications-Tutorial-Step-1
http://fmepedia.safe.com/articles/How_To/FME-Server-Notifications-Tutorial-Step-2
http://fmepedia.safe.com/articles/How_To/Safe-Software-Mobile-Samples
http://fmepedia.safe.com/articles/Samples_and_Demos/Google-Android-Apps
Usage: Setup
Since the hostnames and passwords change for each new FME Cloud instance, you will have to update this template and the associated workspaces. The following instructions list the components that must be updated.
1. Launch an FME Cloud Instance 
  Signup for a FME Cloud account at fmecloud.com
2. Load the configuration into FME Server
Run this workspace with File >  Prompt and Run
Enter the host and password info for your FME Cloud instance
3. Update registerFMEAlertsWithUpdates.fmw
download registerFMEAlertsWithUpdates.fmw
update hostname in: gisdb, FMEServerNotifier, FMEServerNotifier_2, FMEServerNotifier_3
update postgis password in: gisdb
publish
4. Update reportupdatesToFMEAlerts.fmw
download reportupdatesToFMEAlerts.fmw
update hostname in: FeatureReader, FMEServerNotifier
update postgis password: FeatureReader
publish
Mobile Apps
1. Download the FME Reporter and Alerts mobile apps.
2. Configure each app with the:
host: your FME Cloud hostname
username: tutorial-user
password: demo
topic: safe-simple-tracker
3. Report your location from the Reporter app and it will loop through FME Server and back to the Alerts app.
Requirements: FME Cloud
FME Server 2014
History: 2012-02-19,Aaron Koning and Don Murray,Simple tracker created by Don with packaging by Aaron.,2013-11-18,Aaron Koning,Updated to work for FME Cloud and FME SErver 2014
Legal terms conditions: Copyright (c) 2012 Safe Software Inc.
Permission is granted to anyone, free of charge, to use, modify and distribute the object code form of this template for any purpose, subject to the following restrictions:
1) The origin of this template and associated FME(R) software must not be misrepresented.
2) This template may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- new_host = fmepedia2014-safe-software.fmecloud.com   # FME Server host
- new_db_host = demo.me.com   # Enter DB Hostname
- destination_postgres_password =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   # Destination Postgres password

Readers:
- FFS_1: FFS from $(FME_MF_DIR)1b_SubscriberTable.ffs

Writers:
- POSTGIS_1: POSTGIS to demo

Bookmark: Create DB table
public.Subscriber (reader FFS_1)
    attributes: fns_op buffer, fns_version buffer, fns_type buffer, fns_topic buffer, ios_token buffer, gcm_id buffer
    -> safe_notification_tutorial.Subscriber (writer POSTGIS_1)
Note: Drop Table = NO / If there is an existing table of this / name it will not be replaced.
safe_notification_tutorial.Subscriber (writer POSTGIS_1)
    attributes: fns_op text, fns_version text, fns_type text, fns_topic text, ios_token text, gcm_id text

FME custom transformer UniqueValueLogger
This transformer lists all of the unique values for a choosen attrbiute. A count of the number of occurances of each unique value is also displayed. 
This transformer is useful when you are creating a workspace and need to know the possible values to use in a filter.
Add this transformer to your workspace and select the attribute to analyze.
Copyright (c) 2012 Safe Software Inc.
Permission is granted to anyone, free of charge, to use, modify and distribute the object code form of this template for any purpose, subject to the following restrictions:
1) The origin of this template and associated FME(R) software must not be misrepresented.
2) This template may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- VAL =   # Attribute to Analyze

INPUT (input)
    -> AttributeCreator
AttributeCreator
    ATTR_LIST = _log_candidate,$(VAL)
    -> AttributeKeeper

Bookmark: Count and log unique attribute values
AttributeKeeper
    KEEP_ATTRS = _log_candidate
    -> Aggregator
Aggregator
    GROUP_BY = _log_candidate
    ACCUM_ATTRS = Yes
    COUNT_ATTR = _count
    ORDERED = No
    AGGREGATE -> StringConcatenator
StringConcatenator
    PARM_LINE:
      fme_basicstring:1%14%1%22:
      @Value(_count),@Value(_log_candidate)
    VAL_ATTR = _concatenated
    -> Sorter
Sorter
    SORT_PARM = _count NUMERIC DESCENDING _log_candidate ALPHA ASCENDING
    SORTED -> ListBuilder
ListBuilder
    LIST_NAME = _list
    -> ListConcatenator
ListConcatenator
    VAL_ATTR = UNIQUE VALUES
    LIST_ATTR = _list{}._concatenated
    DROP_EMPTY_PARTS = No
    -> ListRemover_2
ListRemover_2
    LIST_ATTRS = _list{}
    -> Logger_2
Logger_2
    MESSAGE = Unique values:
    MAXFEATS = 1
    MAXCOORDS = 1
