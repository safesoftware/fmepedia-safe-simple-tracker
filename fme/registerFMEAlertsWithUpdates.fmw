FME workspace registerFMEAlertsWithUpdates.fmw

Parameters:
- SourceDataset_TEXTLINE = \\tsclient\Downloads\SubscribeiOS.JSON   # Source Text File(s)
- DestDataset_POSTGIS = demo   # Destination PostGIS Dataset

Readers:
- TEXTLINE_1: TEXTLINE from $(SourceDataset_TEXTLINE) in LL-83

Writers:
- POSTGIS_1: POSTGIS to $(DestDataset_POSTGIS) in EPSG:4326

text_line (reader TEXTLINE_1)
    attributes: text_line_data buffer
    -> JSONFlattener
safe_notification_tutorial.Subscriber (writer POSTGIS_1)
    attributes: fns_op text, fns_version text, fns_type text, fns_topic text, ios_token text, gcm_id text

Bookmark: Decode Message to Determine action
JSONFlattener
    RECURSIVE = Yes
    JSON_ATTR = text_line_data
    -> AttributeExposer
AttributeExposer
    ATTR_LIST = fns_op,fns_wkt_geom,fns_type,fns_version,ios_token,gcm_id
    -> ParameterFetcher
ParameterFetcher
    ATTR_LIST = fns_topic {$(FME_TOPIC)}
    -> AttributeRenamer
AttributeFilter
    ATTR_NAME = fns_op
    ATTR_VALUES = report,subscribe,update,unsubscribe,<BLANK>,<UNFILTERED>
    report -> GeometryReplacer
    unsubscribe -> JSONTemplater_2
    update -> GeometryReplacer_2
    subscribe -> GeometryReplacer_3

Bookmark: Use AttributeRenamer to assign default values
AttributeRenamer
    ATTR_LIST = gcm_id,gcm_id,0,ios_token,ios_token,0
    -> PublishTopic
PublishTopic: AttributeCreator
    ATTR_LIST = publish_topic,@Value(fns_topic)-@Value(fns_type)
    -> AttributeFilter
    -> Logger_OUTPUT
Logger_OUTPUT
    MESSAGE = Feature is:
    MAXFEATS = 20
    MAXCOORDS = 20

Bookmark: Location Updates from FME Reporter
GeometryReplacer
    ATTR = fns_wkt_geom
    KIND_LONG = OGC Well Known Text
    -> DB:LocationInsert
DB:LocationInsert: AttributeCreator
    ATTR_LIST = fme_db_operation,insert
    -> FMEServerNotifier_3
FMEServerNotifier_3
    HTTP_UPLOAD_BODY = @Value(text_line_data)
    HTTP_AUTH_PASSWORD =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
    STATUS_CODE_ATTR = _http_status_code
    TOPIC = safe-simple-tracker-update
    HTTP_AUTH_USERNAME = tutorial-author
    URL = https://demo.me.fmecloud.com
    -> safe_notification_tutorial.LocationReportHistory (writer POSTGIS_1) [off]
    -> FMEServerNotifier_3_Output
    <REJECTED> -> FMEServerNotifier_3__Rejected_
safe_notification_tutorial.LocationReportHistory (writer POSTGIS_1)
    attributes: fns_version text, fns_type text, fns_topic text
FMEServerNotifier_3_Output: Inspector [off]

Bookmark: Messages from the FMEAlerts
FMEServerNotifier_3__Rejected_: Inspector [off]
Logger__REJECTED__2
    MESSAGE = Feature is:
    MAXFEATS = 20
    MAXCOORDS = 20
GeographicBufferer
    BufferDist = 500000
    BufferUnit = Meters
    CAP_STYLE = Round
    -> GeographicBufferer_OUTPUT
    -> safe_notification_tutorial.Subscriber (writer POSTGIS_1)
GeographicBufferer_OUTPUT: Inspector [off]
Logger_OUTPUT_2 [off]
    MESSAGE = Feature is:
    MAXFEATS = 20
    MAXCOORDS = 20

Bookmark: Feedback to FMEAlerts - Subscribe
GeometryReplacer_3
    ATTR = fns_wkt_geom
    KIND_LONG = OGC Well Known Text
    -> JSONTemplater_3
JSONTemplater_3
    RESULT_ATTRIBUTE = _result
    CONSECUTIVE_GROUPS = No
    ROOT_QUERY_EXPR:
      {
         "apns_token" : fme:get-attribute("ios_token"),
         "gcm_token"  : fme:get-attribute("gcm_id"),
         "title"      : "Safe Simple Tracker",
         "location"   : fme:get-attribute("fns_wkt_geom"),
         "demo_msg"   : concat("Successfully subscribed to topic ",  fme:get-attribute("fns_topic"), ".")
      }
    VISIBLE_QUERY_VALIDATE = Yes
    -> FMEServerNotifier
FMEServerNotifier
    HTTP_UPLOAD_BODY = @Value(_result)
    HTTP_AUTH_PASSWORD =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
    STATUS_CODE_ATTR = _http_status_code
    TOPIC = @Value(publish_topic)
    HTTP_AUTH_USERNAME = tutorial-author
    URL = https://demo.me.fmecloud.com
    -> DB:subscriber
    <REJECTED> -> Logger__REJECTED__2

Bookmark: Subscriber Register
DB:subscriber: AttributeCreator
    ATTR_LIST = fme_db_operation,insert
    -> GeographicBufferer

Bookmark: Subscriber Location Update
GeometryReplacer_2
    ATTR = fns_wkt_geom
    KIND_LONG = OGC Well Known Text
    -> DB:update_subscriber
DB:update_subscriber: AttributeCreator
    ATTR_LIST = fme_db_operation,update,fme_where,ios_token = '@Value(ios_token)' and gcm_id = '@Value(gcm_id)'
    -> Logger_OUTPUT_2
    -> GeographicBufferer

Bookmark: Feedback to FMEAlerts - Unsubscribe
JSONTemplater_2
    RESULT_ATTRIBUTE = _result
    CONSECUTIVE_GROUPS = No
    ROOT_QUERY_EXPR:
      {
         "apns_token" : fme:get-attribute("ios_token"),
          "gcm_token" : fme:get-attribute("gcm_id"),
          "title"     : "Safe Simple Tracker",
          "demo_msg"  : concat("Successfully unsubscribed to topic ",  fme:get-attribute("fns_topic"), ".")
      }
    VISIBLE_QUERY_VALIDATE = Yes
    -> FMEServerNotifier_2
FMEServerNotifier_2
    HTTP_UPLOAD_BODY = @Value(_result)
    HTTP_AUTH_PASSWORD =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
    STATUS_CODE_ATTR = _http_status_code
    TOPIC = @Value(publish_topic)
    HTTP_AUTH_USERNAME = tutorial-author
    URL = https://demo.me.fmecloud.com
    -> DB:DeleteSubscriiber
    <REJECTED> -> Logger__REJECTED_
Logger__REJECTED_ [off]
    MESSAGE = Feature is:
    MAXFEATS = 20
    MAXCOORDS = 20

Bookmark: Unsubscribe message - Delete
DB:DeleteSubscriiber: AttributeCreator
    ATTR_LIST = fme_db_operation,delete,fme_where,ios_token = '@Value(ios_token)' and gcm_id = '@Value(gcm_id)'
    -> safe_notification_tutorial.Subscriber (writer POSTGIS_1)

FME custom transformer GeographicBufferer
This transformer works much the same way as the standard Bufferer, but is designed for use with features in Geographic coordinates. The transformer reprojects the features into the Dynamic Equal Distance projection, buffers them, then reprojects back into the original Geographic coordinates.
Connect this transformer in your workspace and select appropriate buffer distance unit (Choice between Feet, Miles, Meters, Kilometers), buffer distance amount and buffer end cap style.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- BufferUnit = Meters   # Buffer Distance Unit
- BufferDist = 0   # Buffer Distance
- CAP_STYLE = Round   # End Cap Style

INPUT (input)
    -> CoordinateSystemExtractor
CoordinateSystemExtractor
    CRDSYS_ATTR = _coordsys
    -> Reprojector
Reprojector
    DEST = _AZMED_
    RASTER_CELL_SIZE = Preserve Cells
    STROKE_ARCS = Yes
    SOURCE = Read from feature
    INTERPOLATION_TYPE_NAME = Nearest Neighbor
    REPROJECTED -> ParameterFetcher
ParameterFetcher
    ATTR_LIST = BufferDist {$(BufferDist)} BufferUnit {$(BufferUnit)}
    -> AttributeValueMapper
AttributeValueMapper
    DIRECTION = Forward
    VAL_ATTR = BufferMult
    LUT = Feet,0.3048,Miles,1609.344,Kilometers,1000.0,Meters,1.0,,1.0
    SRC = BufferUnit
    -> ExpressionEvaluator
ExpressionEvaluator
    VAL_ATTR = _buffer
    EXPRESSION = @Value(BufferDist)*@Value(BufferMult)
    -> Bufferer
Bufferer
    INTERP_SEGMENTS = 8
    OFFSET = @Value(_buffer)
    CAP_STYLE = $(CAP_STYLE)
    BUFFERED -> FMEFunctionCaller
FMEFunctionCaller
    FUNC = @Reproject(Read from feature,&_coordsys,NearestNeighbor,PreserveCells)
    -> AttributeRemover
AttributeRemover
    REMOVE_ATTRS = _coordsys,BufferDist,BufferUnit,BufferMult,_buffer
    -> OUTPUT (output)
OUTPUT (output)
