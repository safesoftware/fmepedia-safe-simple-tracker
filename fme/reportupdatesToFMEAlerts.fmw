FME workspace reportupdatesToFMEAlerts.fmw

Parameters:
- SourceDataset_TEXTLINE = \\tsclient\Downloads\reportiOS.json   # Source Text File(s)

Readers:
- TEXTLINE_1: TEXTLINE from $(SourceDataset_TEXTLINE)

text_line (reader TEXTLINE_1)
    attributes: text_line_data buffer
    -> JSONFlattener
JSONFlattener
    RECURSIVE = Yes
    JSON_ATTR = text_line_data
    -> AttributeExposer
AttributeExposer
    ATTR_LIST = fns_op,fns_wkt_geom,fns_topic,fns_type,fns_version,ios_token,gcm_id
    -> GeometryReplacer
GeometryReplacer
    ATTR = fns_wkt_geom
    KIND_LONG = OGC Well Known Text
    -> FeatureReader
FeatureReader
    ATTRIBUTES = safe_notification_tutorial.Subscriber,"fns_op,fns_version,fns_type,fns_topic,ios_token,gcm_id"
    COMBINE_GEOM = In case of conflict, keep INITIATOR geometry
    FORMAT = POSTGIS
    POSTGIS_PORT = 5432
    FEATURETYPES = safe_notification_tutorial.Subscriber
    POSTGIS_TABLELIST = safe_notification_tutorial.Subscriber
    POSTGIS_USER_NAME = demo_me
    POSTGIS_HOST = demo-safe.com
    COMBINE_ATTRS = In case of conflict, keep result attributes
    INTERACT = WITHIN
    SUPPORTED_SPATIAL_INTERACTIONS = ENVELOPE_INTERSECT%INTERSECTS%CONTAINS%CROSSES%DISJOINT%EQUALS%OVERLAPS%TOUCHES%WITHIN
    POSTGIS_DISABLE_COLLECTION_SPLITTING = yes
    POSTGIS_SCHEMALIST = safe_notification_tutorial
    POSTGIS_USE_TRUE_POSTGIS_TYPES = yes
    POSTGIS_PASSWORD =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
    DATASET = demo
    safe_notification_tutorial.Subscriber -> PublishTopic
PublishTopic: AttributeCreator
    ATTR_LIST = publish_topic,@Value(fns_topic)-@Value(fns_type)
    -> JSONTemplater_3
JSONTemplater_3
    VISIBLE_QUERY_VALIDATE = Yes
    RESULT_ATTRIBUTE = _result
    CONSECUTIVE_GROUPS = No
    ROOT_QUERY_EXPR:
      {
         "apns_token" : fme:get-attribute("ios_token"),
         "gcm_token"  : fme:get-attribute("gcm_id"),
         "title"      : "Safe Simple Tracker",
         "location"   : fme:get-attribute("fns_wkt_geom"),
         "demo_msg"   : concat("FME Reporter - location Update activity for topic ",  fme:get-attribute("fns_topic"), "!!")
      }
    -> Logger_public.Subscriber_2
    -> FMEServerNotifier
FMEServerNotifier
    TOPIC = @Value(publish_topic)
    HTTP_AUTH_USERNAME = tutorial-author
    STATUS_CODE_ATTR = _http_status_code
    HTTP_AUTH_PASSWORD =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
    URL = https://tracker-safe-software.fmecloud.com
    HTTP_UPLOAD_BODY = @Value(_result)
    -> Logger_public.Subscriber
    <REJECTED> -> FMEServerNotifier__Rejected_
Logger_public.Subscriber [off]
    MESSAGE = Feature is:
    MAXFEATS = 20
    MAXCOORDS = 20
FMEServerNotifier__Rejected_: Logger
    MESSAGE = Feature is:
    MAXFEATS = 20
    MAXCOORDS = 20
Logger_public.Subscriber_2
    MESSAGE = Feature is:
    MAXFEATS = 20
    MAXCOORDS = 20
