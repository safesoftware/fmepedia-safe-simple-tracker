FME workspace updateDBandStream.fmw

Readers:
- TEXTLINE_1: TEXTLINE from C:\safegit\fmepedia-safe-simple-tracker\JSON\ReportAndroid2.json

Writers:
- POSTGIS_1: POSTGIS to gisdb

text_line (reader TEXTLINE_1)
    attributes: text_line_data buffer
    -> JSONFlattener
JSONFlattener
    RECURSIVE = Yes
    NEW_ATTRIBUTES = msg_last_name msg_first_name fns_wkt_geom msg_url msg_subject msg_content fns_sent msg_from fns_type fns_op
    JSON_ATTR = text_line_data
    -> Tester
Tester
    BOOL_OP = OR
    TEST_CLAUSE = TEST @Value(fns_op) = report
    TEST_MODE = Automatic
    TEST_DESCRIPTION = ""
    PASSED -> BulkAttributeRemover
BulkAttributeRemover
    ATTR_EXP = text_line_
    -> GeometryReplacer
GeometryReplacer
    SOURCE = @Value(fns_wkt_geom)
    KIND_LONG = OGC Well Known Text
    REMOVE_ATTRIBUTE = Yes
    -> safe_notification_tutorial.Event (writer POSTGIS_1)
    -> AttributeRemover
safe_notification_tutorial.Event (writer POSTGIS_1)
    attributes: id serial,PRIKEY, msg_from char(255), msg_last_name char(255), msg_first_name char(255), msg_url char(255), msg_subject char(255), msg_content char(255), fns_sent timestamp, fns_type char(10)
AttributeRemover
    REMOVE_ATTRS = fns_op,fns_type,fns_wkt_geom
    -> GeometryExtractor
GeometryExtractor
    ATTR = geometry
    KIND_LONG = GeoJSON
    -> AttributeRemover_2
AttributeRemover_2
    REMOVE_ATTRS = geojson
    -> AttributeJSONPacker
AttributeJSONPacker
    ATTRS = fns_sent,msg_content,msg_first_name,msg_from,msg_last_name,msg_subject,msg_url
    PACKED = _properties
    -> JSONUpdater [input 2]
Creator
    NUM = 1
    GEOMTYPE = Geometry Object
    CREATED -> JSONUpdater [input 1]
JSONUpdater
    JSON_TYPE = Text or Attribute
    VISIBLE_QUERY_VALIDATE = Yes
    UPDATE_TABLE = GENERATE_JSON_QUERY INSERT_INTO_OBJECT json properties JSON @Value(_properties) GENERATE_JSON_QUERY INSERT_INTO_OBJECT json geometry JSON @Value(geometry)
    RESULT_ATTRIBUTE = geojson
    JSON_TEXT = @Value(geojson)
    DOCUMENT -> WebSocketSender
WebSocketSender
    DATA:
      {
          ws_op: 'send',
          ws_msg: '@Value(geojson)'
      }
    VERIFY_SSL_CERTIFICATES = Yes
    HOST = wss://localhost:7078
    PREAMBLE:
      {
          ws_op: "open",
          ws_stream_id: "simpletracker"
      }

FME custom transformer AttributeJSONPacker
This transformer packs all the attributes that are chosen, or fit the user filter, into a single attribute, as a dictionary in a JSON compatible format:
{"PRI":"2","COMMENTS":"Test Data"}
This is useful for storing multiple format attributes in a single database field for future conversions back to the original format. 
Binary attributes will be hex-encoded and prefaced with "0x". 
Packed attributes can be unpacked using the AttributeJSONUnpacker transformer.
The transformer takes three parameters:
    Attributes to Pack: Specific attributes to pack. Chosing any attributes will disable the filter below.
    Filter Prefix: All attributes with this prefix will be added to the packed attribute. Leaving this value blank will pack all the attributes.
    Packed Attribute Name: The name of the new attribute containing the packed values
Copyright (c) 2014 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- FILTER =   # Filter Prefix (blank for all attributes)
- PACKED = _packed   # Packed Attribute Name
- ATTRS =   # " " Attributes to Pack

INPUT (input)
    -> ParameterFetcher
Note: Get filter value
ParameterFetcher
    ATTR_LIST = AttributeJSONPacker_FILTER {$(FILTER)} AttributeJSONPacker_PACKED {$(PACKED)} AttributeJSONPacker_ATTRS {$(ATTRS)}
    -> PythonCaller
Note: import fmeobjects / import binascii / import json / # This class will create a packed list of format / # attributes suitable for use with @SupplyAttributes() / def packIgdsAtts(feature): / # get a list of attribute names / attlist = feature.getAllAttributeNames() / # get attributes to pack / pack_attrs = feature.getAttribute('AttributeJSONPacker_ATTRS').split(',') / # get filter value / filter = feature.getAttribute('AttributeJSONPacker_FILTER') / # get packed attribute name / packedAtt = feature.getAttribute('AttributeJSONPacker_PACKED') / # disable filter if packed attribute chosen / if pack_attrs[0] != "": / filter = '########################################################################' / # create list for packed attributes / packed = {} / # loop through attribute names / for att in attlist: / # extract only igds format attributes / if (filter in att or att in pack_attrs) and att!='AttributeJSONPacker_ATTRS' and att!='AttributeJSONPacker_FILTER' and att!='AttributeJSONPacker_PACKED': / att_value = feature.getAttribute(att) / # convert binary attributes to hex for storage / if type(att_value) == bytearray: / att_value = "0x" + binascii.hexlify(att_value) / # append attribute value / packed[att] = att_value / # add packed attribute in the form name:value:name:value:name:value... / feature.setAttribute(packedAtt,json.dumps(packed,separators=(',', ':')))
PythonCaller
    NEW_ATTRIBUTES = $(PACKED)
    PYTHONSOURCE:
      import fmeobjects
      import binascii
      import json

      # This class will create a packed list of format
      # attributes suitable for use with @SupplyAttributes()

      def packIgdsAtts(feature):

         # get a list of attribute names
         attlist = feature.getAllAttributeNames()

         # get attributes to pack
         pack_attrs = feature.getAttribute('AttributeJSONPacker_ATTRS').split(',')

         # get filter value
         filter = feature.getAttribute('AttributeJSONPacker_FILTER')


         # get packed attribute name
         packedAtt = feature.getAttribute('AttributeJSONPacker_PACKED')

         # disable filter if packed attribute chosen
         if pack_attrs[0] != "":
             filter = '########################################################################'

         # create list for packed attributes
         packed = {}

         # loop through attribute names
         for att in attlist:
             # extract only igds format attributes
             if (filter in att or att in pack_attrs) and att!='AttributeJSONPacker_ATTRS' and att!='AttributeJSONPacker_FILTER' and att!='AttributeJSONPacker_PACKED':
                 att_value = feature.getAttribute(att)
                 # convert binary attributes to hex for storage
                 if type(att_value) == bytearray:
                     att_value = "0x" + binascii.hexlify(att_value)
                 # append attribute value
                 packed[att] = att_value

         # add packed attribute in the form name:value:name:value:name:value...
         feature.setAttribute(packedAtt,json.dumps(packed,separators=(',', ':')))
    PYTHONSYMBOL = packIgdsAtts
    -> AttributeRemover
Note: Remove temporary attributes
AttributeRemover
    REMOVE_ATTRS = AttributeJSONPacker_FILTER,AttributeJSONPacker_PACKED,AttributeJSONPacker_ATTRS
    -> OUTPUT (output)
OUTPUT (output)
